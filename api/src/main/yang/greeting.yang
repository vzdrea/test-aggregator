module greeting {
  namespace "urn:opendaylight:greeting";
  prefix grt;
  revision "2018-07-02" {
    description "Greet module";
  }
  rpc small-greet {
        input {
            leaf name {
                 type string;
            }

        }
        output {
            leaf result {
                type string;
            }
        }
  }


  notification big-greet{
    leaf desc {
        type string;
    }
  }

   container message-data {
    container news{
    leaf name {
    type string;
    }
    }
    leaf location {
        type string;
    }
    leaf weather {
        type string;
    }

 }
}
